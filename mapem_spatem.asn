MAPEM-PDU-Descriptions {
 itu-t (0) identified-organization (4) etsi (0) itsDomain (5) wg1 (1) en (103301) mapem (1)
version1 (1)
}
DEFINITIONS AUTOMATIC TAGS ::= 

BEGIN

IMPORTS
MapData FROM DSRC { iso (1) standard (0) signalizedIntersection (19091) profilec(2) dsrc (2) version
(1) }
ItsPduHeader FROM ITS-Container 
{ itu-t (0) identified-organization (4) etsi (0) itsDomain (5) wg1 (1) ts (102894) cdd (2) version (2)};


MAPEM ::= SEQUENCE {
 header ItsPduHeader,
 map MapData
}

END

SPATEM-PDU-Descriptions {
 itu-t (0) identified-organization (4) etsi (0) itsDomain (5) wg1 (1) en (103301) spatem (0)
version1 (1)
}
DEFINITIONS AUTOMATIC TAGS ::=

BEGIN

IMPORTS
SPAT FROM DSRC { iso (1) standard (0) signalizedIntersection (19091) profilec(2) dsrc (2) version
(1) }
ItsPduHeader FROM ITS-Container
{ itu-t (0) identified-organization (4) etsi (0) itsDomain (5) wg1 (1) ts (102894) cdd (2) version (2) };

SPATEM ::= SEQUENCE {
 header ItsPduHeader,
 spat SPAT
}

END

--  >>>>>>>>>>>>>>>>>>>>>>>>>><<<<<<<<<<<<<<<<<<<<<<<<<<
--  >>>>>>>>>>>>>>>>>> ITS-Container  <<<<<<<<<<<<<<<<<<  
--  >>>>>>>>>>>>>>>>>>>>>>>>>><<<<<<<<<<<<<<<<<<<<<<<<<<
ITS-Container {
itu-t (0) identified-organization (4) etsi (0) itsDomain (5) wg1 (1) ts (102894) cdd (2) version (2)}

DEFINITIONS AUTOMATIC TAGS ::=

BEGIN
ItsPduHeader ::= SEQUENCE {
    protocolVersion INTEGER (0..255),
    messageID INTEGER{ denm(1), cam(2), poi(3), spatem(4), mapem(5), ivim(6), ev-rsr(7), tistpgtransaction(8), srem(9), ssem(10), evcsn(11), saem(12), rtcmem(13) } (0..255),  -- Mantis #7209, #7005
    stationID StationID
}

StationID ::= INTEGER(0..4294967295)

Longitude ::= INTEGER {oneMicrodegreeEast (10), oneMicrodegreeWest (-10), unavailable(1800000001)} (-1800000000..1800000001)

Latitude ::= INTEGER {oneMicrodegreeNorth (10), oneMicrodegreeSouth (-10), unavailable(900000001)} (-900000000..900000001)

SpeedConfidence ::= INTEGER {equalOrWithinOneCentimeterPerSec(1), equalOrWithinOneMeterPerSec(100), outOfRange(126), unavailable(127)} (1..127)

Altitude ::= SEQUENCE {
    altitudeValue AltitudeValue,
    altitudeConfidence AltitudeConfidence
}

AltitudeValue ::= INTEGER {referenceEllipsoidSurface(0), oneCentimeter(1), unavailable(800001)} (-100000..800001)

AltitudeConfidence ::= ENUMERATED {
    alt-000-01 (0),
    alt-000-02 (1),
    alt-000-05 (2),
    alt-000-10 (3),
    alt-000-20 (4),
    alt-000-50 (5),
    alt-001-00 (6),
    alt-002-00 (7),
    alt-005-00 (8),
    alt-010-00 (9),
    alt-020-00 (10),
    alt-050-00 (11),
    alt-100-00 (12),
    alt-200-00 (13),
    outOfRange (14),
    unavailable (15)
}

DeltaAltitude ::= INTEGER {oneCentimeterUp (1), oneCentimeterDown (-1), unavailable(12800)} (-12700..12800)


END


-- ^-^-^-^-^-^-^-^-^-^-^-^-^-^-^-^-^-^-^-^-^-^-^-^-^-^-^-^-
-- 
-- module: DSRC
-- 
-- ^-^-^-^-^-^-^-^-^-^-^-^-^-^-^-^-^-^-^-^-^-^-^-^-^-^-^-^-
DSRC { iso (1) standard (0) signalizedIntersection (19091) profilec(2) dsrc (2) version (1) } 

DEFINITIONS AUTOMATIC TAGS::= BEGIN 

IMPORTS
StationID, Longitude, Latitude, SpeedConfidence FROM ITS-Container 
{ itu-t (0) identified-organization (4) etsi (0) itsDomain (5) wg1 (1) ts (102894) cdd (2) version (2) };

-- -_-_-_-_-_-_-_-_-_-_-_-_-_-_-_-_-_-_-_-_-_-_-_-_-_-_-_-_
-- 
-- Start of entries from table Messages...
-- This table typicaly contains message entries.
-- -_-_-_-_-_-_-_-_-_-_-_-_-_-_-_-_-_-_-_-_-_-_-_-_-_-_-_-_
-- 

-- Regional extensions support

RegionalExtension ::= SEQUENCE {
   regionId [0]     RegionId,
   regExtValue[1]  ANY DEFINED BY regionId  -- hack to avoid RegExt and empty unions
   }
 
SPAT ::= SEQUENCE { 
   timeStamp     MinuteOfTheYear OPTIONAL,  
   name          DescriptiveName OPTIONAL, 
                 -- human readable name for this collection 
                 -- to be used only in debug mode
   
   intersections IntersectionStateList,
                 -- sets of SPAT data (one per intersection)  
   
   -- If PrioritizationResponse data is required, it is found 
   -- in the RegionalSPAT entry below
   
   regional      SEQUENCE (SIZE(1..4)) OF 
                 RegionalExtension OPTIONAL,
   ...
   }


MapData ::= SEQUENCE {
   timeStamp         MinuteOfTheYear OPTIONAL, 
   msgIssueRevision  MsgCount,        
   layerType         LayerType OPTIONAL,
   layerID           LayerID  OPTIONAL,
   intersections     IntersectionGeometryList OPTIONAL,
                     -- All Intersection definitions 
   roadSegments      RoadSegmentList OPTIONAL,
                     -- All roadway descriptions
  
   dataParameters    DataParameters OPTIONAL,
                     -- Any meta data regarding the map contents
   
   restrictionList   RestrictionClassList OPTIONAL,
                     -- Any restriction ID tables which have  
                     -- established for these map entries 
   regional          SEQUENCE (SIZE(1..4)) OF 
                     RegionalExtension OPTIONAL,
   
   -- NOTE:
   -- Other map data will be added here as it is defined
   -- Examples of the type of content to be added include
   -- curve warnings, construction routes, etc.
   ...
}


-- -_-_-_-_-_-_-_-_-_-_-_-_-_-_-_-_-_-_-_-_-_-_-_-_-_-_-_-_
-- 
-- Start of entries from table Data_Frames...
-- This table typicaly contains data frame entries.
-- -_-_-_-_-_-_-_-_-_-_-_-_-_-_-_-_-_-_-_-_-_-_-_-_-_-_-_-_
-- 

AdvisorySpeed ::= SEQUENCE {
   type        AdvisorySpeedType,
               -- the type of advisory which this is.
   speed       SpeedAdvice OPTIONAL,
               -- See Section 11 for converting and translating speed 
               -- expressed in mph into units of m/s
               -- This element is optional ONLY when superceded 
               -- by the presence of a regional speed element found in
               -- Reg-AdvisorySpeed entry
   confidence  SpeedConfidence OPTIONAL,
               -- A confidence value for the above speed
   distance    ZoneLength OPTIONAL,
               -- Unit = 1 meter,  
               -- The distance indicates the region for which the advised speed 
               -- is recommended, it is specified upstream from the stop bar  
               -- along the connected egressing lane
   class       RestrictionClassID OPTIONAL,
               -- the vehicle types to which it applies
               -- when absent, the AdvisorySpeed applies to
               -- all motor vehicle types
   regional    SEQUENCE (SIZE(1..4)) OF 
               RegionalExtension OPTIONAL,
   ...
   }

AdvisorySpeedList ::= SEQUENCE (SIZE(1..16)) OF AdvisorySpeed

ComputedLane ::= SEQUENCE {
   -- Data needed to created a computed lane
   referenceLaneId    LaneID,
                         -- the lane ID upon which this 
                         -- computed lane will be based 
   -- Lane Offset in X and Y direction
   offsetXaxis        CHOICE {
                         small   DrivenLineOffsetSm, 
                         large   DrivenLineOffsetLg
                         },  
   offsetYaxis        CHOICE {
                         small   DrivenLineOffsetSm, 
                         large   DrivenLineOffsetLg
                         },  
                         -- A path X offset value for translations of the 
                         -- path's points when creating translated lanes. 
                         -- The values found in the reference lane are 
                         -- all offset based on the X and Y values from 
                         -- the coordinates of the reference lane's 
                         -- initial path point.   
   -- Lane Rotation
   rotateXY           Angle OPTIONAL, 
                         -- A path rotation value for the entire lane
                         -- Observe that this rotates the existing orientation 
                         -- of the referenced lane, it does not replace it.
                         -- Rotation occurs about the initial path point.
   -- Lane Path Scale (zooming)
   scaleXaxis         Scale-B12 OPTIONAL, 
   scaleYaxis         Scale-B12 OPTIONAL, 
                         -- value for translations or zooming of the path's 
                         -- points. The values found in the reference lane 
                         -- are all expanded or contracted based on the X 
                         -- and Y and width values from the coordinates of 
                         -- the reference lane's initial path point.  
                         -- The Z axis remains untouched.  
   regional  SEQUENCE (SIZE(1..4)) OF 
             RegionalExtension OPTIONAL,
   ... 
   }
ConnectsToList ::= SEQUENCE (SIZE(1..16)) OF Connection

ConnectingLane ::= SEQUENCE {
   lane      LaneID,   -- Index of the connecting lane
   maneuver  AllowedManeuvers OPTIONAL
                       -- The Maneuver between 
                       -- the enclosing lane and this lane
                       -- at the stop line to connect them
   }


Connection ::= SEQUENCE {
   -- The subject lane connecting to this lane is:
   connectingLane     ConnectingLane, 
                      -- The index of the connecting lane and also
                      -- the maneuver from the current lane to it
   remoteIntersection IntersectionReferenceID OPTIONAL,  
                      -- This entry is only used when the 
                      -- indicated connecting lane belongs 
                      -- to another intersection layout. This 
                      -- provides a means to create meshes of lanes
   
   -- SPAT mapping details at the stop line are:
   signalGroup        SignalGroupID OPTIONAL,    
                      -- The matching signal group send by 
                      -- the SPAT message for this lane/maneuver.
                      -- Shall be present unless the connectingLane 
                      -- has no signal group (is un-signalized)
   userClass          RestrictionClassID OPTIONAL, 
                      -- The Restriction Class of users this applies to
                      -- The use of some lane/maneuver and SignalGroupID 
                      -- pairings are restricted to selected users.
                      -- When absent, the SignalGroupID applies to all
   
   -- Movement assist details are given by:
   connectionID       LaneConnectionID OPTIONAL
                      -- An optional connection index used to 
                      -- relate this lane connection to any dynamic 
                      -- clearance data in the SPAT. Note that
                      -- the index may be shared with other 
                      -- connections if the clearance data is common
   }


ConnectionManeuverAssist ::= SEQUENCE {
   connectionID         LaneConnectionID,
                        -- the common connectionID used by all lanes to which
                        -- this data applies 
                        -- (this value traces to ConnectsTo entries in lanes)
   -- Expected Clearance Information
   queueLength          ZoneLength OPTIONAL,
                        -- Unit = 1 meter, 0 = no queue
                        -- The distance from the stop line to the back 
                        -- edge of the last vehicle in the queue,                     
                        -- as measured along the lane center line.
   availableStorageLength ZoneLength OPTIONAL,
                        -- Unit = 1 meter, 0 = no space remains
                        -- Distance (e.g. beginning from the downstream 
                        -- stop-line up to a given distance) with a high 
                        -- probability for successfully executing the 
                        -- connecting maneuver between the two lanes 
                        -- during the current cycle. 
                        -- Used for enhancing the awareness of vehicles 
                        -- to anticipate if they can pass the stop line
                        -- of the lane. Used for optimizing the green wave, 
                        -- due to knowledge of vehicles waiting in front 
                        -- of a red light (downstream).
                        -- The element nextTime in TimeChangeDetails
                        -- in the containing data frame contains the next 
                        -- timemark at which an active phase is expected, 
                        -- a form of storage flush interval.
   waitOnStop           WaitOnStopline OPTIONAL,
                        -- If "true", the vehicles on this specific connecting 
                        -- maneuver have to stop on the stop-line and not 
                        -- to enter the collision area 
   pedBicycleDetect     PedestrianBicycleDetect OPTIONAL,
                        -- true if ANY ped or bicycles are detected crossing 
                        -- the above lanes. Set to false ONLY if there is a 
                        -- high certainty that there are none present, 
                        -- otherwise element is not sent.
   regional  SEQUENCE (SIZE(1..4)) OF 
             RegionalExtension OPTIONAL,
   ...  
   }

DataParameters ::= SEQUENCE {
   processMethod     IA5String(SIZE(1..255)) OPTIONAL, 
   processAgency     IA5String(SIZE(1..255)) OPTIONAL, 
   lastCheckedDate   IA5String(SIZE(1..255)) OPTIONAL, 
   geoidUsed         IA5String(SIZE(1..255)) OPTIONAL, 
   ...  
   }

EnabledLaneList ::= SEQUENCE (SIZE(1..16)) OF LaneID
   -- The unique ID numbers for each
   -- lane object which is 'active' 
   -- as part of the dynamic map contents.

GenericLane ::= SEQUENCE { 
   laneID           LaneID, 
                    -- The unique ID number assigned 
                    -- to this lane object
   name             DescriptiveName OPTIONAL,        
                    -- often for debug use only 
                    -- but at times used to name ped crossings
   ingressApproach  ApproachID OPTIONAL, -- inbound
   egressApproach   ApproachID OPTIONAL, -- outbound
                    -- Approach IDs to which this lane belongs
   laneAttributes   LaneAttributes, 
                    -- All Attribute information about 
                    -- the basic selected lane type
                    -- Directions of use, Geometric co-sharing
                    -- and Type Specific Attributes
                    -- These Attributes are 'lane - global' that is,
                    -- they are true for the entire length of the lane
   maneuvers        AllowedManeuvers OPTIONAL,
                    -- the permitted maneuvers for this lane
   nodeList         NodeListXY,
                    -- Lane spatial path information as well as
                    -- various Attribute information along the node path  
                    -- Attributes found here are more general and may
                    -- come and go over the length of the lane.
   connectsTo       ConnectsToList OPTIONAL, 
                    -- a list of other lanes and their signal group IDs
                    -- each connecting lane and its signal group ID
                    -- is given, therefore this element provides the
                    -- information formerly in "signalGroups" in prior
                    -- editions.
   overlays         OverlayLaneList OPTIONAL, 
                    -- A list of any lanes which have spatial paths that
                    -- overlay (run on top of, and not simply cross) 
                    -- the path of this lane when used
   regional  SEQUENCE (SIZE(1..4)) OF 
             RegionalExtension OPTIONAL,
   ...
   }


IntersectionGeometry ::= SEQUENCE {
   name        DescriptiveName OPTIONAL, 
                            -- For debug use only
   id          IntersectionReferenceID,  
                            -- A globally unique value set, 
                            -- consisting of a regionID and 
                            -- intersection ID assignment
   revision    MsgCount,    

   -- Required default values about lane descriptions follow
   refPoint    Position3D,  -- The reference from which subsequent 
                            -- data points are offset until a new
                            -- point is used. 
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given 
                            -- See Section 11 for converting and 
                            -- translating speed expressed in mph 
                            -- into units of m/s
   -- Complete details regarding each lane type in this intersection
   laneSet     LaneList,    -- Data about one or more lanes
                            -- (all lane data is found here)
   
   -- Data describing how to use and request preemption and
   -- priority services from this intersection (if supported)
   -- NOTE Additonal data may be added in the next release of the 
   -- standard at this point to handle this concept
   preemptPriorityData PreemptPriorityList OPTIONAL, 
                           -- data about one or more regional
                           -- preempt or priority zones 
   
   regional     SEQUENCE (SIZE(1..4)) OF 
                RegionalExtension OPTIONAL,
   ... 
   }

IntersectionGeometryList ::= SEQUENCE (SIZE(1..32)) OF IntersectionGeometry
   
IntersectionReferenceID ::= SEQUENCE {
   region  RoadRegulatorID OPTIONAL,
           -- a globally unique regional assignment value
           -- typical assigned to a regional DOT authority
           -- the value zero shall be used for testing needs
   id      IntersectionID
           -- a unique mapping to the intersection
           -- in question within the above region of use
   }
   
IntersectionState ::= SEQUENCE {
   name         DescriptiveName OPTIONAL, 
                -- human readable name for intersection  
                -- to be used only in debug mode
   id           IntersectionReferenceID,  
                -- A globally unique value set, consisting of a 
                -- regionID and intersection ID assignment
                -- provides a unique mapping to the 
                -- intersection MAP in question
                -- which provides complete location 
                -- and approach/move/lane data
   revision     MsgCount,    
   status       IntersectionStatusObject,
                -- general status of the controller(s)
   moy          MinuteOfTheYear OPTIONAL,
                -- Minute of current UTC year
                -- used only with messages to be archived 
   timeStamp    DSecond OPTIONAL, 
                -- the mSec point in the current UTC minute that
                -- this message was constructed
   enabledLanes EnabledLaneList OPTIONAL,  
                -- a list of lanes where the RevocableLane bit 
                -- has been set which are now active and 
                -- therefore part of the current intersection
   states       MovementList,
                -- Each Movement is given in turn
                -- and contains its signal phase state, 
                -- mapping to the lanes it applies to, and
                -- point in time it will end, and it
                -- may contain both active and future states 
   maneuverAssistList  ManeuverAssistList OPTIONAL,
                -- Assist data
   
   regional     SEQUENCE (SIZE(1..4)) OF 
                RegionalExtension OPTIONAL,
   ... 
   }
   
IntersectionStateList ::= SEQUENCE (SIZE(1..32)) OF  IntersectionState

LaneAttributes ::= SEQUENCE {
   directionalUse  LaneDirection,      -- directions of lane use
   sharedWith      LaneSharing,        -- co-users of the lane path
   laneType        LaneTypeAttributes, -- specific lane type data
   regional        RegionalExtension OPTIONAL
   }

LaneDataAttribute ::= CHOICE {
    -- Segment attribute types and the data needed for each
    pathEndPointAngle        DeltaAngle,  
                             -- adjusts final point/width slant
                             -- of the lane to align with the stop line
    laneCrownPointCenter     RoadwayCrownAngle,  
                             -- sets the canter of the road bed      
                             -- from centerline point
    laneCrownPointLeft       RoadwayCrownAngle,  
                             -- sets the canter of the road bed
                             -- from left edge
    laneCrownPointRight      RoadwayCrownAngle,  
                             -- sets the canter of the road bed
                             -- from right edge
    laneAngle                MergeDivergeNodeAngle,  
                             -- the angle or direction of another lane
                             -- this is required to support Japan style
                             -- when a merge point angle is required
    speedLimits              SpeedLimitList,
                             -- Reference regulatory speed limits
                             -- used by all segments
   
    -- Add others as needed, in regional space
    regional  SEQUENCE (SIZE(1..4)) OF 
              RegionalExtension, 
    ...
    }

LaneDataAttributeList ::= SEQUENCE (SIZE(1..8)) OF LaneDataAttribute

LaneList ::= SEQUENCE (SIZE(1..255)) OF GenericLane

LaneSharing ::= BIT STRING {
    -- With bits as defined:
    overlappingLaneDescriptionProvided  (0),
    -- Assert when another lane object is present to describe the
    -- path of the overlapping shared lane
    -- this construct is not used for lane objects which simply cross
    multipleLanesTreatedAsOneLane       (1),
    -- Assert if the lane object path and width details represents
    -- multiple lanes within it that are not further described

    -- Various modes and type of traffic that may share this lane:
    otherNonMotorizedTrafficTypes       (2), -- horse drawn etc.
    individualMotorizedVehicleTraffic   (3),
    busVehicleTraffic                   (4),  
    taxiVehicleTraffic                  (5),
    pedestriansTraffic                  (6),
    cyclistVehicleTraffic               (7),
    trackedVehicleTraffic               (8),
    pedestrianTraffic                   (9)
    } (SIZE (10))
    -- All zeros would indicate 'not shared' and 'not overlapping'

LaneTypeAttributes ::= CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   }

ManeuverAssistList ::= SEQUENCE (SIZE(1..16)) OF ConnectionManeuverAssist

MovementEventList ::= SEQUENCE (SIZE(1..16)) OF MovementEvent

MovementEvent ::= SEQUENCE {
   eventState   MovementPhaseState,
                -- Consisting of:
                -- Phase state (the basic 11 states)
                -- Directional, protected, or permissive state
   
   timing       TimeChangeDetails OPTIONAL,
                -- Timing Data in UTC time stamps for event
                -- includes start and min/max end times of phase
                -- confidence and estimated next occurrence
   
   speeds       AdvisorySpeedList OPTIONAL,
                -- various speed advisories for use by
                -- general and specific types of vehicles
                -- supporting green-wave and other flow needs
                -- See Section 11 for converting and translating 
                -- speed expressed in mph into units of m/s

   regional     SEQUENCE (SIZE(1..4)) OF 
                RegionalExtension OPTIONAL,
   ...  
   }

MovementList ::= SEQUENCE (SIZE(1..255)) OF MovementState

MovementState ::= SEQUENCE {
   movementName       DescriptiveName OPTIONAL,
                      -- uniquely defines movement by name   
                      -- human readable name for intersection  
                      -- to be used only in debug mode
   signalGroup        SignalGroupID,    
                      -- the group id is used to map to lists 
                      -- of lanes (and their descriptions) 
                      -- which this MovementState data applies to 
                      -- see comments in the Remarks for usage details 
   state-time-speed   MovementEventList,   
                      -- Consisting of sets of movement data with:
                      -- a)  SignalPhaseState
                      -- b)  TimeChangeDetails,  and 
                      -- c)  AdvisorySpeeds      (optional )
                      -- Note one or more of the movement events may be for 
                      -- a future time and that this allows conveying multiple 
                      -- predictive phase and movement timing for various uses
                      -- for the current signal group
   maneuverAssistList ManeuverAssistList OPTIONAL,
                      -- This information may also be placed in the 
                      -- IntersectionState when common information applies to
                      -- different lanes in the same way
   regional           SEQUENCE (SIZE(1..4)) OF 
                      RegionalExtension OPTIONAL,
   ...  
   }

NodeAttributeSetXY ::= SEQUENCE {
   localNode    NodeAttributeXYList OPTIONAL,
                -- Attribute states which pertain to this node point
   disabled     SegmentAttributeXYList OPTIONAL,
                -- Attribute states which are disabled at this node point
   enabled      SegmentAttributeXYList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation 
                -- at this node from this node onwards, in 10cm steps
                -- elevations between nodes are a linear taper between pts
                -- the value of zero shall not be sent here
   regional     SEQUENCE (SIZE(1..4)) OF 
                RegionalExtension OPTIONAL,
   ...
   }

NodeAttributeXYList ::= SEQUENCE (SIZE(1..8)) OF NodeAttributeXY

NodeAttributeXY ::= ENUMERATED {
   -- Various values which pertain only to the current node point
   
   -- General Items
   reserved,  
   stopLine,             -- point where a mid-path stop line exists
                         -- See also 'do not block' for segments

   -- Path finish details 
   roundedCapStyleA,      -- Used to control final path rounded end shape
                          -- with edge of curve at final point in a circle
   roundedCapStyleB,      -- Used to control final path rounded end shape
                          -- with edge of curve extending 50% of width past
                          -- final point in a circle
   
   -- Topography Points (items with no concept of a distance along the path)
   mergePoint,           -- Japan merge with 1 or more lanes
   divergePoint,         -- Japan diverge with 1 or more lanes
   downstreamStopLine,   -- Japan style downstream intersection 
                                   -- (a 2nd intersection) stop line
   downstreamStartNode,  -- Japan style downstream intersection 
                                   -- (a 2nd intersection) start node
     
   -- Pedestrian Support Attributes
   closedToTraffic,      -- where a pedestrian may NOT go
                         -- to be used during construction events
   safeIsland,           -- a pedestrian safe stopping point
                         -- also called a traffic island
                         -- This usage described a point feature on a path, 
                         -- other entries can describe a path
   curbPresentAtStepOff, -- the sidewalk to street curb is NOT 
                         -- angled where it meets the edge of the 
                         -- roadway (user must step up/down)
 
   -- Lane geometry details  (see standard for defined shapes)
   hydrantPresent,       -- Or other services access 
   ...
   }

Node-LLmD-64b ::= SEQUENCE {
   lon  Longitude,
   lat  Latitude
   }

   Node-XY-20b ::= SEQUENCE {
   x  Offset-B10,
   y  Offset-B10
   }

Node-XY-22b ::= SEQUENCE {
   x  Offset-B11,
   y  Offset-B11
   }


Node-XY-24b ::= SEQUENCE {
   x  Offset-B12,
   y  Offset-B12
   }


Node-XY-26b ::= SEQUENCE {
   x  Offset-B13,
   y  Offset-B13
   }


Node-XY-28b ::= SEQUENCE {
   x  Offset-B14,
   y  Offset-B14
   }


Node-XY-32b ::= SEQUENCE {
   x  Offset-B16,
   y  Offset-B16
   }

NodeListXY ::= CHOICE {
   nodes     NodeSetXY,
             -- a lane made up of two or more
             -- XY node points and any attributes 
             -- defined in those nodes
   computed  ComputedLane,
             -- a lane path computed by translating 
             -- the data defined by another lane
   ...
   }

NodeOffsetPointXY ::= CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   regional         RegionalExtension
                                    -- node which follows is of a 
                                    -- regional definition type 
   }

NodeSetXY ::= SEQUENCE (SIZE(2..63)) OF NodeXY

NodeXY ::= SEQUENCE {
   delta       NodeOffsetPointXY,
               -- A choice of which X,Y offset value to use  
               -- this includes various delta values as well a regional choices
   attributes  NodeAttributeSetXY OPTIONAL,
               -- Any optional Attributes which are needed
               -- This includes changes to the current lane width and elevation
   ... 
}

OverlayLaneList ::= SEQUENCE (SIZE(1..5)) OF LaneID
   -- The unique ID numbers for any lane object which have
   -- spatial paths that overlay (run on top of, and not
   -- simply cross with) the current lane.
   -- Such as a train path that overlays a motor vehicle
   -- lane object for a roadway segment.

Position3D ::= SEQUENCE {
   lat        Latitude,                -- in 1/10th micro degrees
   long       Longitude,               -- in 1/10th micro degrees
   elevation  Elevation  OPTIONAL,     -- in 10 cm units
   regional   SEQUENCE (SIZE(1..4)) OF 
              RegionalExtension OPTIONAL,
   ...
   }

PreemptPriorityList ::= SEQUENCE (SIZE(1..32)) OF SignalControlZone

RegulatorySpeedLimit ::= SEQUENCE {
   type        SpeedLimitType, 
               -- The type of regulatory speed which follows
   speed       Velocity
               -- The speed in units of 0.02 m/s
               -- See Section 11 for converting and translating 
               -- speed expressed in mph into units of m/s
   }


RestrictionClassAssignment ::= SEQUENCE {
   id       RestrictionClassID,
            -- the unique value (within an intersection or local region)
            -- that is assigned to this group of users
   users    RestrictionUserTypeList 
            -- The list of user types/classes 
            -- to which this restriction ID applies
   }

RestrictionClassList ::= SEQUENCE (SIZE(1..254)) OF RestrictionClassAssignment

RestrictionUserTypeList ::= SEQUENCE (SIZE(1..16)) OF  RestrictionUserType

RestrictionUserType ::= CHOICE {
   basicType   RestrictionAppliesTo,
               -- a set of the most commonly used types
   regional    SEQUENCE (SIZE(1..4)) OF 
               RegionalExtension, 
   ...
   }

RoadLaneSetList ::= SEQUENCE (SIZE(1..255)) OF GenericLane

RoadSegmentReferenceID ::= SEQUENCE {
   region  RoadRegulatorID OPTIONAL,
           -- a globally unique regional assignment value
           -- typically assigned to a regional DOT authority
           -- the value zero shall be used for testing needs
   id      RoadSegmentID
           -- a unique mapping to the road segment
           -- in question within the above region of use
           -- during its period of assignment and use
           -- note that unlike intersectionID values, 
           -- this value can be reused by the region
   }

RoadSegment ::= SEQUENCE {
   name        DescriptiveName OPTIONAL,
   id          RoadSegmentReferenceID,
                           -- a globally unique value for the segment
   revision    MsgCount,    
   -- Required default values about the descriptions to follow
   refPoint    Position3D, -- the reference from which subsequent
                           -- data points are offset until a new
                           -- point is used.
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given   
                            -- See Section 11 for converting and  
                            -- translating speed expressed in mph 
                            -- into units of m/s
                         
   -- Data describing disruptions in the RoadSegment
   -- such as work zones etc will be added here;
   -- in the US the SAE ITIS codes would be used here
   -- The details regarding each lane type in the RoadSegment
   roadLaneSet RoadLaneSetList,   
  
   regional    SEQUENCE (SIZE(1..4)) OF 
               RegionalExtension OPTIONAL,
   ...
   }

RoadSegmentList ::= SEQUENCE (SIZE(1..32)) OF RoadSegment
   
SegmentAttributeXYList ::= SEQUENCE (SIZE(1..8)) OF SegmentAttributeXY

SignalControlZone ::=  SEQUENCE {
  zone  RegionalExtension,
  ...
  }



   
SpeedLimitList ::= SEQUENCE (SIZE(1..9)) OF RegulatorySpeedLimit

SpeedLimitType ::= ENUMERATED {
    unknown,                    -- Speed limit type not available
    maxSpeedInSchoolZone,       -- Only sent when the limit is active
    maxSpeedInSchoolZoneWhenChildrenArePresent, -- Sent at any time
    maxSpeedInConstructionZone, -- Used for work zones, incident zones, etc.
                                -- where a reduced speed is present
    vehicleMinSpeed,
    vehicleMaxSpeed,            -- Regulatory speed limit for general traffic
    vehicleNightMaxSpeed,

    truckMinSpeed,
    truckMaxSpeed,
    truckNightMaxSpeed,

    vehiclesWithTrailersMinSpeed,
    vehiclesWithTrailersMaxSpeed,
    vehiclesWithTrailersNightMaxSpeed,
    ...
    }

TimeChangeDetails ::= SEQUENCE {
   startTime   TimeMark           OPTIONAL,
               -- When this phase 1st started
   minEndTime  TimeMark,
               -- Expected shortest end time
   maxEndTime  TimeMark           OPTIONAL,
               -- Expected longest end time
   
   likelyTime  TimeMark           OPTIONAL,
               -- Best predicted value based on other data              
   confidence  TimeIntervalConfidence OPTIONAL,
               -- Applies to above time element only
   
   nextTime    TimeMark           OPTIONAL
               -- A rough estimate of time when 
               -- this phase may next occur again
               -- used to support various ECO driving power 
               -- management needs.
   }

TimeMark ::= INTEGER (0..36001)
   -- Tenths of a second in the current or next hour
   -- In units of 1/10th second from UTC time
   -- A range of 0~36000 covers one hour
   -- The values 35991..36000 are used when a leap second occurs
   -- The value 36001 is used to indicate time >3600 seconds
   -- 36002 is to be used when value undefined or unknown
   -- Note that this is NOT expressed in GPS time
   -- or in local time

   
-- -_-_-_-_-_-_-_-_-_-_-_-_-_-_-_-_-_-_-_-_-_-_-_-_-_-_-_-_
-- 
-- Start of entries from table Data_Elements...
-- This table typicaly contains data element entries.
-- -_-_-_-_-_-_-_-_-_-_-_-_-_-_-_-_-_-_-_-_-_-_-_-_-_-_-_-_
--    

AdvisorySpeedType ::= ENUMERATED {
    none       (0),
    greenwave  (1),
    ecoDrive   (2),
    transit    (3),
    ...  
    } -- Note: subject to further growth

AllowedManeuvers ::= BIT STRING {
    -- With bits as defined:
    -- Allowed maneuvers at path end (stop line)
    -- All maneuvers with bits not set are therefore prohibited !
    -- A value of zero shall be used for unknown, indicating no Maneuver
    maneuverStraightAllowed      (0), 
                                  -- a Straight movement is allowed in this lane
    maneuverLeftAllowed          (1),  
                                 -- a Left Turn movement is allowed in this lane
    maneuverRightAllowed         (2), 
                                 -- a Right Turn movement is allowed in this lane
    maneuverUTurnAllowed         (3), 
                                 -- a U turn movement is allowed in this lane
    maneuverLeftTurnOnRedAllowed (4), 
                                 -- a Stop, and then proceed when safe movement 
                                 -- is allowed in this lane  
    maneuverRightTurnOnRedAllowed (5), 
                                 -- a Stop, and then proceed when safe movement 
                                 -- is allowed in this lane  
    maneuverLaneChangeAllowed    (6), 
                                 -- a movement which changes to an outer lane 
                                 -- on the egress side is allowed in this lane
                                 -- (example: left into either outbound lane)
    maneuverNoStoppingAllowed    (7), 
                                 -- the vehicle should not stop at the stop line
                                 -- (example: a flashing green arrow)
    yieldAllwaysRequired         (8), 
                                 -- the allowed movements above are not protected 
                                 -- (example: an permanent yellow condition)
    goWithHalt                   (9), 
                                 -- after making a full stop, may proceed
    caution                      (10), 
                                 -- proceed past stop line with caution
    reserved1                    (11)
                                 -- used to align to 12 Bit Field
   
   } (SIZE(12))

Angle ::= INTEGER (0..28800) 
   -- LSB of 0.0125 degrees
   -- A range of 0 to 359.9875 degrees

ApproachID ::= INTEGER (0..15) -- zero to be used when valid value is unknown
   

DeltaAngle ::= INTEGER (-150..150) 
   -- With an angle range from 
   -- negative 150 to positive 150 
   -- in one degree steps where zero is directly
   -- along the axis or the lane center line as defined by the
   -- two closest points

DescriptiveName ::= IA5String (SIZE(1..63))

DrivenLineOffsetLg ::= INTEGER (-32767..32767) 
   -- LSB units are 1 cm.

DrivenLineOffsetSm ::= INTEGER (-2047..2047) 
   -- LSB units are 1 cm.

DSecond ::= INTEGER (0..65535) -- units of milliseconds
  
Elevation ::= INTEGER (-4096..61439) 
  -- In units of 10 cm steps above or below the reference ellipsoid 
  -- Providing a range of -409.5 to + 6143.9 meters 
  -- The value -4096 shall be used when Unknown is to be sent

IntersectionID ::= INTEGER (0..65535)
   -- The values zero through 255 are allocated for testing purposes
   -- Note that the value assigned to an intersection will be
   -- unique within a given regional ID only

IntersectionStatusObject ::= BIT STRING {
    manualControlIsEnabled                (0),
      -- Timing reported is per programmed values, etc. but person
      -- at cabinet can manually request that certain intervals are
      -- terminated early (e.g. green).
    stopTimeIsActivated                   (1),
      -- And all counting/timing has stopped.
    failureFlash                          (2), 
      -- Above to be used for any detected hardware failures, 
      -- e.g. conflict monitor as well as for police flash 
    preemptIsActive                       (3),
    signalPriorityIsActive                (4),   
	 
   -- Additional states
    fixedTimeOperation                    (5),
      -- Schedule of signals is based on time only 
      -- (i.e. the state can be calculated)
    trafficDependentOperation             (6),
      -- Operation is based on different levels of traffic parameters 
      -- (requests, duration of gaps or more complex parameters)
    standbyOperation                      (7),
      -- Controller: partially switched off or partially amber flashing
    failureMode                           (8),
      -- Controller has a problem or failure in operation
    off                                   (9),
      -- Controller is switched off
	 
   -- Related to MAP and SPAT bindings
    recentMAPmessageUpdate                (10),
      -- Map revision with content changes
    recentChangeInMAPassignedLanesIDsUsed (11),
      -- Change in MAP's assigned lanes used (lane changes)
      -- Changes in the active lane list description
    noValidMAPisAvailableAtThisTime       (12),
      -- MAP (and various lanes indexes) not available
    noValidSPATisAvailableAtThisTime      (13)
      -- SPAT system is not working at this time
    
    -- Bits 14,15 reserved at this time and shall be zero
    } (SIZE(16))


LaneAttributes-Barrier ::= BIT STRING {
   -- With bits as defined:
   median-RevocableLane     (0),
                            -- this lane may be activated or not based
                            -- on the current SPAT message contents
                            -- if not asserted, the lane is ALWAYS present
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))

LaneAttributes-Bike ::= BIT STRING {
   -- With bits as defined:
   bikeRevocableLane       (0),
                           -- this lane may be activated or not based
                           -- on the current SPAT message contents
                           -- if not asserted, the lane is ALWAYS present
   pedestrianUseAllowed    (1),
                           -- The path allows pedestrian traffic, 
                           -- if not set, this mode is prohibited
   isBikeFlyOverLane       (2),
                           -- path of lane is not at grade
   fixedCycleTime          (3),
                           -- the phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entries
                           -- in the Connect follow this same pattern in pairs.
   isolatedByBarrier       (5),
   unsignalizedSegmentsPresent  (6)
                           -- The lane path consists of one of more segments
                           -- which are not part of a signal group ID

   -- Bits 7~15 reserved and set to zero
   } (SIZE (16))

LaneAttributes-Crosswalk ::= BIT STRING { 
   -- With bits as defined:
   -- MUTCD provides no suitable "types" to use here
   crosswalkRevocableLane  (0),
                           -- this lane may be activated or not based
                           -- on the current SPAT message contents
                           -- if not asserted, the lane is ALWAYS present
   bicyleUseAllowed        (1),
                           -- The path allows bicycle traffic, 
                           -- if not set, this mode is prohibited
   isXwalkFlyOverLane      (2),
                           -- path of lane is not at grade
   fixedCycleTime          (3),
                           -- ped walk phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entries
                           -- in the Connect follow this same pattern in pairs.
   hasPushToWalkButton     (5),
                           -- Has a demand input
   audioSupport            (6),
                           -- audio crossing cues present
   rfSignalRequestPresent  (7),
                           -- Supports RF push to walk technologies
   unsignalizedSegmentsPresent  (8)
                           -- The lane path consists of one of more segments
                           -- which are not part of a signal group ID
   -- Bits 9~15 reserved and set to zero
   } (SIZE (16))

LaneAttributes-Parking ::= BIT STRING { 
    -- With bits as defined:
    -- Parking use details, note that detailed restrictions such as 
    -- allowed hours are sent by way of ITIS codes in the TIM message
    parkingRevocableLane         (0),
                                 -- this lane may be activated or not based
                                 -- on the current SPAT message contents
                                 -- if not asserted, the lane is ALWAYS present
    parallelParkingInUse         (1),
    headInParkingInUse           (2),
    doNotParkZone                (3),
                                 -- used to denote fire hydrants as well as
                                 -- short disruptions in a parking zone
    parkingForBusUse             (4),
    parkingForTaxiUse            (5),
    noPublicParkingUse           (6)
                                 -- private parking, as in front of
                                 -- private property
   -- Bits 7~15 reserved and set to zero
   } (SIZE (16))

LaneAttributes-Sidewalk ::= BIT STRING { 
   -- With bits as defined:
   sidewalk-RevocableLane  (0),
                           -- this lane may be activated or not based
                           -- on the current SPAT message contents
                           -- if not asserted, the lane is ALWAYS present
   bicyleUseAllowed        (1),
                           -- The path allows bicycle traffic, 
                           -- if not set, this mode is prohibited
   isSidewalkFlyOverLane   (2),
                           -- path of lane is not at grade
   walkBikes               (3)
                           -- bike traffic must dismount and walk
   -- Bits 4~15 reserved and set to zero
   } (SIZE (16))


LaneAttributes-Striping ::= BIT STRING { 
   -- With bits as defined:
    stripeToConnectingLanesRevocableLane      (0),
       -- this lane may be activated or not activated based
       -- on the current SPAT message contents
       -- if not asserted, the lane is ALWAYS present
    stripeDrawOnLeft                          (1),
    stripeDrawOnRight                         (2),
        -- which side of lane to mark
    stripeToConnectingLanesLeft               (3),
    stripeToConnectingLanesRight              (4),
    stripeToConnectingLanesAhead              (5)
        -- the stripe type should be
        -- presented to the user visually
        -- to reflect stripes in the 
        -- intersection for the type of
        -- movement indicated
   -- Bits 6~15 reserved and set to zero
   } (SIZE (16))


LaneAttributes-TrackedVehicle ::= BIT STRING { 
   -- With bits as defined:
   spec-RevocableLane         (0),
                               -- this lane may be activated or not based
                               -- on the current SPAT message contents
                               -- if not asserted, the lane is ALWAYS present
   spec-commuterRailRoadTrack (1), 
   spec-lightRailRoadTrack    (2),
   spec-heavyRailRoadTrack    (3),
   spec-otherRailType         (4)
   -- Bits 5~15 reserved and set to zero
   } (SIZE (16))


LaneAttributes-Vehicle ::= BIT STRING {  
   -- With bits as defined:
   isVehicleRevocableLane       (0),
                                 -- this lane may be activated or not based
                                 -- on the current SPAT message contents
                                 -- if not asserted, the lane is ALWAYS present
   isVehicleFlyOverLane         (1),
                                 -- path of lane is not at grade
   hovLaneUseOnly               (2),
   restrictedToBusUse           (3),
   restrictedToTaxiUse          (4),
   restrictedFromPublicUse      (5),
   hasIRbeaconCoverage          (6),
   permissionOnRequest          (7) -- e.g. to inform about a lane for e-cars

   } (SIZE (8,...))

LaneConnectionID ::= INTEGER (0..255)

LaneDirection ::= BIT STRING {
   -- With bits as defined:
   -- Allowed directions of travel in the lane object
   -- All lanes are described from the stop line outwards
   ingressPath     (0), 
                   -- travel from rear of path to front 
                   -- is allowed
   egressPath      (1)
                   -- travel from front of path to rear 
                   -- is allowed
   -- Notes:  No Travel, i.e. the lane object type does not support
   --         travel (medians, curbs, etc.) is indicated by not 
   --         asserting any bit value
   --         Bi-Directional Travel (such as a ped crosswalk) is 
   --         indicated by asserting both of the bits
   } (SIZE (2))

LaneID ::= INTEGER (0..255)
   -- the value 0 shall be used when the lane ID is
   -- not available or not known
   -- the value 255 is reserved for future use

LayerID ::= INTEGER (0..100)

LayerType ::= ENUMERATED {
     none, 
     mixedContent, -- two or more of the below types
     generalMapData, 
     intersectionData, 
     curveData, 
     roadwaySectionData, 
     parkingAreaData, 
     sharedLaneData,
     ... 
     }
   
LaneWidth ::= INTEGER (0..32767) -- units of 1 cm

MergeDivergeNodeAngle ::= INTEGER (-180..180) 
   -- In units of 1.5 degrees from north
   -- the value -180 shall be used to represent 
   -- data is not available or unknown

MinuteOfTheYear ::= INTEGER (0..527040) 
   -- the value 527040 shall be used for invalid

MovementPhaseState ::= ENUMERATED {
    -- Note that based on the regions and the operating mode not every 
    -- phase will be used in all transportation modes and that not 
    -- every phase will be used in all transportation modes
  
    unavailable (0), 
      -- This state is used for unknown or error 
    dark (1),   
      -- The signal head is dark (unlit)

   -- Reds
    stop-Then-Proceed (2), 
      -- Often called 'flashing red' in US
      -- Driver Action:                     
      --   Stop vehicle at stop line. 
      --   Do not proceed unless it is safe.
      -- Note that the right to proceed either right or left when 
      -- it is safe may be contained in the lane description to 
      -- handle what is called a 'right on red'
    stop-And-Remain (3),
      -- e.g. called 'red light' in US
      -- Driver Action:                     
      --   Stop vehicle at stop line. 
      --   Do not proceed.                     
      -- Note that the right to proceed either right or left when 
      -- it is safe may be contained in the lane description to 
      -- handle what is called a 'right on red'
   
   -- Greens
    pre-Movement (4), 
      -- Not used in the US, red+yellow partly in EU
      -- Driver Action:                     
      --   Stop vehicle. 
      --   Prepare to proceed (pending green)
      --   (Prepare for transition to green/go)
    permissive-Movement-Allowed (5), 
      -- Often called 'permissive green' in US
      -- Driver Action:                     
      --   Proceed with caution, 
      --   must yield to all conflicting traffic 
      -- Conflicting traffic may be present
      -- in the intersection conflict area
    protected-Movement-Allowed (6), 
      -- Often called 'protected green' in US
      -- Driver Action:                     
      --   Proceed, tossing caution to the wind, 
      --   in indicated (allowed) direction.
   
   -- Yellows / Ambers
   -- The vehicle is not allowed to cross the stop bar if it is possible 
   -- to stop without danger. 
    permissive-clearance (7), 
      -- Often called 'permissive yellow' in US
      -- Driver Action:                     
      --   Prepare to stop.
      --   Proceed if unable to stop,
      --   Clear Intersection.
      -- Conflicting traffic may be present
      -- in the intersection conflict area
    protected-clearance (8),  
      -- Often called 'protected yellow' in US
      -- Driver Action: 
      --   Prepare to stop.
      --   Proceed if unable to stop,
      --   in indicated direction (to connected lane)
      --   Clear Intersection.
                    
    caution-Conflicting-Traffic (9)
      -- Often called 'flashing yellow' in US
      -- Often used for extended periods of time
      -- Driver Action: 
      --   Proceed with caution, 
      -- Conflicting traffic may be present
      -- in the intersection conflict area
    }
    -- The above number assignments are not used with UPER encoding
    -- and are only to be used with DER or implicit encoding

MsgCount ::= INTEGER (0..127)

Offset-B10 ::= INTEGER (-512..511)
   -- a range of +- 5.11 meters

Offset-B11 ::= INTEGER (-1024..1023)
   -- a range of +- 10.23 meters

Offset-B12 ::= INTEGER (-2048..2047)
   -- a range of +- 20.47 meters

Offset-B13 ::= INTEGER (-4096..4095)
   -- a range of +- 40.95 meters

Offset-B14 ::= INTEGER (-8192..8191)
   -- a range of +- 81.91 meters

Offset-B16 ::= INTEGER (-32768..32767)
   -- a range of +- 327.68 meters

PedestrianBicycleDetect ::= BOOLEAN 
                 -- true if ANY Pedestrians or Bicyclists are 
                 -- detected crossing the target lane or lanes
   
PrioritizationResponseStatus ::= ENUMERATED {
   unknown           (0),
                      -- Unknown state
   requested         (1),
                      -- This prioritization request was detected 
                      -- by the traffic controller  
   processing        (2),
                      -- Checking request 
                      -- (request is in queue, other requests are prior)
   watchOtherTraffic (3),
                      -- Cannot give full permission, 
                      -- therefore watch for other traffic
                      -- Note that other requests may be present
   granted           (4),
                      -- Intervention was successful 
                      -- and now prioritization is active
   rejected          (5),
                      -- The prioritization or preemption request was 
                      -- rejected by the traffic controller
   maxPresence       (6),
                      -- The Request has exceeded maxPresence time
                      -- Used when the controller has determined that
                      -- the requester should then back off and 
                      -- request an alternative.  
   reserviceLocked   (7),
                      -- Prior conditions have resulted in a reservice 
                      -- locked event: the controller requires the 
                      -- passage of time before another similar request 
                      -- will be accepted
   ...
}


RegionId ::= INTEGER (0..255)
   noRegion     RegionId ::= 0  -- Use default supplied stubs
   addGrpA      RegionId ::= 1  -- USA
   addGrpB      RegionId ::= 2  -- Japan
   addGrpC      RegionId ::= 3  -- EU
   -- NOTE: new registered regional IDs will be added here
   -- The values 128 and above are for local region use

RestrictionAppliesTo ::= ENUMERATED {
    none,              -- applies to nothing
    equippedTransit,   -- buses etc.
    equippedTaxis,
    equippedOther,     -- other vehicle types with
                       -- necessary signal phase state
                       -- reception equipment
    emissionCompliant, -- regional variants with more
                       -- definitive items also exist
    equippedBicycle,
    weightCompliant,
    heightCompliant,
    -- Items dealing with traveler needs serviced by the infrastructure
    -- These end users (which are not vehicles) are presumed to be suitably equipped
    pedestrians,
    slowMovingPersons,
    wheelchairUsers,
    visualDisabilities,
    audioDisabilities,  -- hearing
    otherUnknownDisabilities,
    ...
    }

RestrictionClassID ::= INTEGER (0..255)
   -- An index value to identify data about classes of users
   -- the value used varies with each intersection's
   -- needs and is defined in the map to the assigned 
   -- classes of supported users.

RoadRegulatorID ::= INTEGER (0..65535)
   -- The value zero shall be used for testing only

RoadSegmentID ::= INTEGER (0..65535)
   -- The values zero to 255 shall be used for testing only
   -- Note that the value assigned to an RoadSegment will be
   -- unique within a given regional ID only during its use

RoadwayCrownAngle ::= INTEGER (-128..127) 
    -- In LSB units of 0.3 degrees of angle
    -- over a range of -38.1 to + 38.1 degrees
    -- The value -128 shall be used for unknown
    -- The value zero shall be used for angles 
    -- which are between -0.15 and +0.15
   
Scale-B12 ::= INTEGER (-2048..2047)  -- in steps of 0.05 percent

SignalGroupID ::= INTEGER (0..255) 
    -- The value 0 shall be used when the ID is
    -- not available or not known
    -- the value 255 is reserved to indicate a 
    -- permanent green movement state
    -- therefore a simple 8 phase signal controller 
    -- device might use 1..9 as its groupIDs

SegmentAttributeXY ::= ENUMERATED {
   -- Various values which can be Enabled and Disabled for a lane segment
   
   -- General Items
   reserved                  ,  
   doNotBlock                ,  -- segment where a vehicle 
                                -- may not come to a stop
   whiteLine                 ,  -- segment where lane crossing not allowed
                                -- such as the final few meters of a lane
   
   -- Porous Lane states, merging, turn outs, parking etc.
   
   mergingLaneLeft           ,  -- indicates porous lanes
   mergingLaneRight          ,
   
   curbOnLeft                ,  -- indicates presence of curbs
   curbOnRight               ,
   
   loadingzoneOnLeft         ,  -- loading or drop off zones
   loadingzoneOnRight        ,
   
   turnOutPointOnLeft        ,  -- opening to adjacent street/alley/road
   turnOutPointOnRight       ,
   
   adjacentParkingOnLeft     , -- side of road parking
   adjacentParkingOnRight    ,
   
   -- Bike Lane Needs
   adjacentBikeLaneOnLeft    , -- presence of marked bike lanes
   adjacentBikeLaneOnRight   ,
   sharedBikeLane            , -- right of way is shared with bikes
                               -- who may occupy entire lane width
   bikeBoxInFront            ,
   
   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley 
                               -- not used for crossing tracks
  
     
   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb 
                               -- but at least 1 meter remains open for use
                               -- and at-grade passage
   
   -- Lane geometry details  (see standard for defined shapes)
   taperToLeft               , -- Used to control final path shape
   taperToRight              , -- Used to control final path shape
   taperToCenterLine         , -- Used to control final path shape

   -- Parking Lane and Curb Attributes
   parallelParking           , -- 
   headInParking             , -- Parking at an angle with the street
   freeParking               , -- no restriction on use of parking
   timeRestrictionsOnParking , -- Parking is not permitted at all times
                               -- typically used when the 'parking' lane 
                               -- becomes a driving lane at times
   costToPark                , -- Used where parking has a cost
   midBlockCurbPresent       , -- a protruding curb near lane edge
   unEvenPavementPresent     , -- a disjoint height at lane edge
   ...
   }

SpeedAdvice ::= INTEGER (0..500) 
    -- LSB units are 0.1 m/s^2
    -- the value 499 shall be used for values at or greater than 49.9 m/s
    -- the value 500 shall be used to indicate that speed is unavailable


TimeIntervalConfidence ::= INTEGER (0..15)   
   -- Value   Probability
   --   0         21%
   --   1         36%
   --   2         47%
   --   3         56%
   --   4         62%
   --   5         68%
   --   6         73%
   --   7         77%
   --   8         81%
   --   9         85%
   --   10        88%
   --   11        91%
   --   12        94%
   --   13        96%
   --   14        98%
   --   15        100%


Velocity ::= INTEGER (0..8191) -- Units of 0.02 m/s
    -- The value 8191 indicates that 
    -- velocity is unavailable

WaitOnStopline ::= BOOLEAN -- 
         -- True or False
         -- If "true", the vehicles on this specific connecting 
         -- maneuver have to stop on the stop-line
         -- and not to enter the collision area

ZoneLength ::= INTEGER (0..10000)
    -- Unit = 1 meter, 0 = unknown, 
    -- The value 10000 to be used for Distances >=10000 m
    -- (e.g. from known point to another point along a 
    -- known path, often against traffic flow direction 
    -- when used for measuring queues)

END
